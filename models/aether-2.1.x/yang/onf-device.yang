// SPDX-FileCopyrightText: 2022-present Intel Corporation
// SPDX-FileCopyrightText: 2021 Open Networking Foundation
//
// SPDX-License-Identifier: Apache-2.0
submodule onf-device {
  belongs-to onf-site {
    prefix site;
  }

  import ietf-yang-types {
    prefix yang;
  }
  import onf-aether-types {
    prefix at;
  }
  include onf-sim-card;

  organization
    "Open Networking Foundation.";
  contact
    "ROC Engineering";
  description
    "A Aether Device...";

  revision 2022-01-19 {
    description
      "An Aether Device";
    reference
      "RFC 6087";
  }

  typedef device-id {
    type at:aether-identifier;
    description
      "The typedef for device-id";
  }

  grouping device {
    description
      "The top level container";
    list device {
      key "device-id";
      unique "imei";
      description
        "List of devices";
      leaf device-id {
        type device-id;
        description
          "ID for this device.";
      }
      uses at:desc-display-name;
      leaf imei {
        type at:imei;
        description
          "IMEI for this device";
      }
      // TODO: Device Type
      leaf sim-card {
        type leafref {
          path "../../sim-card/sim-id";
        }
        description
          "Link to simcard";
      }
      container state {
        config false;
        description
          "read only attributes of device";
        leaf ip-address {
          type string;
          description
            "the ip address assigned to the device";
        }
        leaf connected {
          type string {
            pattern 'Yes|No|Idle';
          }
          description
            "the connected status (Yes|No|Idle)";
        }
        leaf last-connected {
          type yang:date-and-time;
          description
            "The time in UTC that the device was last connected";
        }
      }
    }
  }
}
